Keystore DEFINITIONS EXPLICIT TAGS ::=
  BEGIN
    KeyStore ::= SEQUENCE {
      version         INTEGER,
      xcs             BOOLEAN,
      db              KeyStoreDB
    }
    KeyStoreDB ::=  SEQUENCE OF KeyStoreEntry
    KeyStoreEntry ::= SEQUENCE {
      domain      INTEGER,
      data        KeyStoreEntryData
    }
    KeyStoreEntryData ::= CHOICE {
      -- DER Encoded X509 certificate - Opaque to keystore implementation.
      certificate    [0]  KeyStoreCertificate,
      -- DER Encoding of "public key", RSA/EC  - Opaque to keystore implementation
      publickey      [1]  KeyStorePublicKey
    }
    KeyStoreCertificate     ::=  OCTET STRING
    KeyStorePublicKey       ::=  OCTET STRING
  END
